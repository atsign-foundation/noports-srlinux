// Phase 2 starter: makes sshnpd configurable from the SR Linux CLI/gNMI.
//
// Not wired up by default — uncomment the yang-modules section in
// appmgr/sshnpd.yml to enable, and extend run-sshnpd.sh (or a small NDK
// agent) to consume the delivered JSON config instead of sshnpd.env.
module noports-sshnpd {
    yang-version 1.1;
    namespace "https://atsign.com/yang/noports-sshnpd";
    prefix noports;

    organization "Atsign";
    description "NoPorts sshnpd configuration for Nokia SR Linux";

    revision 2026-07-09 {
        description "Initial scaffold";
    }

    container sshnpd {
        presence "Enable the NoPorts sshnpd daemon";

        leaf device-atsign {
            type string {
                pattern '@.+';
            }
            mandatory true;
            description "The atSign identifying this router";
        }

        leaf-list manager-atsigns {
            type string {
                pattern '@.+';
            }
            min-elements 1;
            description "atSigns permitted to connect to this router";
        }

        leaf device-name {
            type string {
                length "1..36";
                pattern '[a-z0-9_]+';
            }
            mandatory true;
            description "Device name clients use: sshnp -d <device-name>";
        }

        leaf key-file {
            type string;
            default "/etc/opt/sshnpd/keys/device.atKeys";
            description "Path to the atKeys file for device-atsign";
        }

        container state {
            config false;
            description "Operational state published by the agent";

            leaf oper-state {
                type enumeration {
                    enum up;
                    enum down;
                    enum connecting;
                }
            }
            leaf last-heartbeat {
                type string;
                description "Timestamp of the last atServer heartbeat";
            }
        }
    }
}
