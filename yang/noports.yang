// NoPorts as a native SR Linux feature: this module puts the full sshnpd
// configuration surface in the router config tree (CLI/gNMI/JSON-RPC) and
// its operational state in the state tree. The structure mirrors the
// sections of NoPorts' own config file (sshnpd.yaml), which noports-agent
// renders to /etc/opt/noports/sshnpd.yaml on every commit and feeds to
// sshnpd via --config.
module noports {
    yang-version 1.1;
    namespace "https://atsign.com/yang/noports";
    prefix noports;

    organization "Atsign";
    description "NoPorts (sshnpd) configuration and state for Nokia SR Linux";

    revision 2026-07-10 {
        description
            "Model the full sshnpd.yaml schema: access/device/ssh/runtime
             sections; agent renders the NoPorts config file";
    }

    typedef atsign {
        type string {
            pattern '@.+';
        }
        description "An Atsign, including the leading @";
    }

    container noports {
        description "NoPorts daemon: SSH/npt access with no listening ports";

        leaf admin-state {
            type enumeration {
                enum enable;
                enum disable;
            }
            default "disable";
            description
                "Enable or disable the NoPorts daemon. Requires
                 device-atsign and at least one of access/managers or
                 access/policy.";
        }

        leaf device-atsign {
            type atsign;
            description "The Atsign identifying this router";
        }

        leaf root-server {
            type string;
            default "root.atsign.org";
            description
                "atDirectory server. Use the form proxy:<host>:443 to send
                 all atProtocol traffic to a reverse proxy on one port when
                 management-plane ACLs restrict egress.";
        }

        leaf key-file {
            type string;
            default "/etc/opt/noports/keys/device.atKeys";
            description
                "Path to the APKAM atKeys file, created on the router by
                 /opt/noports/onboard-noports.sh";
        }

        container access {
            description "Who may connect, and to what";

            leaf-list managers {
                type atsign;
                description
                    "Atsigns with direct access to this router (permit-open
                     applies; policy is ignored for managers)";
            }

            leaf policy {
                type atsign;
                description
                    "Atsign of a NoPorts policy service for fine-grained,
                     delegated authorization";
            }

            leaf-list permit-open {
                type string;
                description
                    "host:port pairs clients may reach, e.g. localhost:22
                     and localhost:57400 (gNMI). Empty means the NoPorts
                     defaults (localhost:22, localhost:3389 without policy;
                     *:* with policy).";
            }
        }

        container device {
            description "Device identity as seen by NoPorts clients";

            leaf name {
                type string {
                    length "1..36";
                    pattern '[a-zA-Z0-9_]+';
                }
                description "Device name clients use: sshnp -d <name>";
            }

            leaf group {
                type string;
                description "Device group name, used for fleet management";
            }
        }

        container ssh {
            description "How sessions reach the local sshd";

            leaf add-public-keys {
                type boolean;
                default true;
                description
                    "Update authorized_keys with the session public key sent
                     by the manager (sshnpd.yaml: ssh/add-publickeys)";
            }

            leaf ssh-client {
                type enumeration {
                    enum openssh;
                    enum dart;
                }
                default "openssh";
                description "Client used for outbound ssh connections";
            }

            leaf sshd-port {
                type uint16;
                default 22;
                description "Port sshd listens on (internal interface)";
            }

            leaf-list public-key-permissions {
                type string;
                description
                    "Options prefixed to authorized_keys entries added via
                     add-public-keys (see sshd AUTHORIZED KEYS FILE FORMAT)";
            }
        }

        container runtime {
            description "Daemon runtime settings";

            leaf verbose {
                type boolean;
                default true;
                description "INFO-level sshnpd logging";
            }

            leaf clear-cached-pks {
                type boolean;
                default false;
                description
                    "Clear the cached public keys on next start (use after
                     resetting an Atsign)";
            }
        }

        container state {
            config false;
            description "Operational state published by noports-agent";

            leaf oper-state {
                type string;
                description
                    "disabled | not-configured | awaiting-onboarding |
                     running | retrying";
            }
            leaf message {
                type string;
                description "Human-readable detail for the current state";
            }
            leaf pid {
                type uint32;
                description "PID of the running sshnpd process";
            }
            leaf sshnpd-version {
                type string;
                description "Version reported by the packaged sshnpd binary";
            }
        }
    }
}
